// AUTO-GENERATED by sf-sysml — DO NOT HAND-EDIT.
// Source of truth: requirements/requirement-map.yml
// Edit the YAML and re-run; this file regenerates from it.
// Mapping spec: dev-docs/architecture/sysml-export.md

package SystemsFirstTemplate {

    // Bring SysMLv2 primitive scalar types (Real, String, Integer,
    // Boolean, etc.) into scope so attribute types resolve in Syson /
    // Cameo / any conformant parser.
    import ScalarValues::*;

    // ======= User Needs =======

    // -- User Need: UN-001 --
    requirement def UN_001 {
        doc /* UN-001 */
    }

    // -- User Need: UN-002 --
    requirement def UN_002 {
        doc /* UN-002 */
    }

    // ======= Verification Cases (Stages) =======

    // -- Verification Case: Stage 1 — Scaffold & Foundation --
    verification case def Stage_1___Scaffold___Foundation {
        doc /* Stage 1 — Scaffold & Foundation */
        // verifies: UN_001
        // verifies: UN_002
    }

    // -- Verification Case: Stage 2 — Core Engine --
    verification case def Stage_2___Core_Engine {
        doc /* Stage 2 — Core Engine */
    }
}
